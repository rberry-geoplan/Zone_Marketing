FME workspace StreetLookup_step2.fmw

Parameters:
- DestDataset_CSV2 = C:\Data\Zone   # Destination CSV (Comma Separated Value) Folder
- DestDataset_CSV2_3 = $(FME_MF_DIR)StreetLookup   # Destination CSV (Comma Separated Value) Folder
- SourceDataset_MAPINFO = ""$(FME_MF_DIR)StreetLookup\gbrg30___________nw_Step1_Outv4.tab" "$(FME_MF_DIR)StreetLookup\gbrg29___________nw_Step1_Outv4.tab" "$(FME_MF_DIR)StreetLookup\gbrg28___________nw_Step1_Outv4.tab" "$(FME_MF_DIR)StreetLookup\gbrg27___________nw_Step1_Outv4.tab" "$(FME_MF_DIR)StreetLookup\gbrg26___________nw_Step1_Outv4.tab" "$(FME_MF_DIR)StreetLookup\gbrg24___________nw_Step1_Outv4.tab" "$(FME_MF_DIR)StreetLookup\gbrg23___________nw_Step1_Outv4.tab" "$(FME_MF_DIR)StreetLookup\gbrg21___________nw_Step1_Outv4.tab""   # Source MapInfo TAB File(s)

Readers:
- MAPINFO_1: MAPINFO from $(SourceDataset_MAPINFO)

Writers:
- CSV2_1: CSV2 to $(DestDataset_CSV2)
- CSV2_2: CSV2 to $(DestDataset_CSV2_3)

gbrg29___________nw_Step1_Outv4 (reader MAPINFO_1)
    attributes: NAME char(100), ID decimal(15,0), PLACENAME char(99), ADMIN char(99), _related_candidates char(99), Start_x char(99), Start_y char(99), End_x char(99), End_y char(99), SHIELDNUM char(7)
    -> GeometryRemover
gbrg30___________nw_Step1_Outv4 (reader MAPINFO_1)
    attributes: NAME char(100), ID decimal(15,0), PLACENAME char(99), ADMIN char(99), _related_candidates char(99), Start_x char(99), Start_y char(99), End_x char(99), End_y char(99), SHIELDNUM char(7)
    -> GeometryRemover
gbrg27___________nw_Step1_Outv4 (reader MAPINFO_1)
    attributes: NAME char(100), ID decimal(15,0), PLACENAME char(99), ADMIN char(99), _related_candidates char(99), Start_x char(99), Start_y char(99), End_x char(99), End_y char(99), SHIELDNUM char(7)
    -> GeometryRemover
gbrg23___________nw_Step1_Outv4 (reader MAPINFO_1)
    attributes: NAME char(100), ID decimal(15,0), PLACENAME char(99), ADMIN char(99), _related_candidates char(99), Start_x char(99), Start_y char(99), End_x char(99), End_y char(99), SHIELDNUM char(7)
    -> GeometryRemover
gbrg28___________nw_Step1_Outv4 (reader MAPINFO_1)
    attributes: NAME char(100), ID decimal(15,0), PLACENAME char(99), ADMIN char(99), _related_candidates char(99), Start_x char(99), Start_y char(99), End_x char(99), End_y char(99), SHIELDNUM char(7)
    -> GeometryRemover
gbrg26___________nw_Step1_Outv4 (reader MAPINFO_1)
    attributes: NAME char(100), ID decimal(15,0), PLACENAME char(99), ADMIN char(99), _related_candidates char(99), Start_x char(99), Start_y char(99), End_x char(99), End_y char(99), SHIELDNUM char(7)
    -> GeometryRemover
gbrg24___________nw_Step1_Outv4 (reader MAPINFO_1)
    attributes: NAME char(100), ID decimal(15,0), PLACENAME char(99), ADMIN char(99), _related_candidates char(99), Start_x char(99), Start_y char(99), End_x char(99), End_y char(99), SHIELDNUM char(7)
    -> GeometryRemover
gbrg21___________nw_Step1_Outv4 (reader MAPINFO_1)
    attributes: NAME char(100), ID decimal(15,0), PLACENAME char(99), ADMIN char(99), _related_candidates char(99), Start_x char(99), Start_y char(99), End_x char(99), End_y char(99), SHIELDNUM char(7)
    -> GeometryRemover
GeometryRemover
    -> TestFilter
TestFilter
    TEST_LIST = BOOL_OP,OR,COMPOSITE_TEST,<Unused>,TEST_CLAUSE,"TEST @Value(NAME) = Guiseran Road",@Value(NAME) = Guiseran Road
    DEFAULT_VALUE = <UNFILTERED>
    @Value(NAME) = Guiseran Road -> AttributeCreator
    <UNFILTERED> -> AttributeCreator
AttributeCreator
    ATTR_TABLE = SET_TO NAME_CAPS = @Value(NAME)
    -> StringCaseChanger
StringCaseChanger
    CHANGE_TYPE = UPPERCASE
    ATTRCHOICE = Selected Attributes
    ATTRLIST = NAME_CAPS
    -> StatisticsCalculator
StatisticsCalculator
    MEDIAN_ATTR = _median
    PREPEND_ATTR_NAME_CHOICE = For multiple results only
    MIN_ATTR = _min
    MAX_ATTR = _max
    COMPUTE_HISTOGRAM = NO
    STATS_ATTRS = End_x End_y
    COUNT_ATTR = COUNT
    GROUP_BY = ADMIN PLACENAME NAME_CAPS
    COMPLETE -> TestFilter_5
TestFilter_5
    TEST_LIST:
      BOOL_OP,AND,COMPOSITE_TEST,<Unused>,TEST_CLAUSE,"TEST @Value(ADMIN) ATTRIBUTE_HAS_VALUE """"
      TEST @Value(PLACENAME) ATTRIBUTE_HAS_VALUE """"",ADMIN  AND PLACENAME ATTRIBUTE_HAS_VALUE,BOOL_OP,AND,COMPOSITE_TEST,<Unused>,TEST_CLAUSE,"TEST @Value(PLACENAME) ATTRIBUTE_HAS_VALUE """"
      TEST ADMIN ATTRIBUTE_IS_MISSING """"",PLACENAME ONLY ATTRIBUTE_HAS_VALUE,BOOL_OP,AND,COMPOSITE_TEST,<Unused>,TEST_CLAUSE,"TEST @Value(PLACENAME) ATTRIBUTE_HAS_VALUE """"
      TEST ADMIN ATTRIBUTE_IS_EMPTY """"",PLACENAME ONLY ATTRIBUTE_HAS_VALUE,BOOL_OP,AND,COMPOSITE_TEST,<Unused>,TEST_CLAUSE,"TEST PLACENAME ATTRIBUTE_IS_MISSING """"
      TEST @Value(ADMIN) ATTRIBUTE_HAS_VALUE """"",ADMIN ONLY ATTRIBUTE_HAS_VALUE,BOOL_OP,AND,COMPOSITE_TEST,<Unused>,TEST_CLAUSE,"TEST PLACENAME ATTRIBUTE_IS_EMPTY """"
      TEST @Value(ADMIN) ATTRIBUTE_HAS_VALUE """"",ADMIN ONLY ATTRIBUTE_HAS_VALUE,BOOL_OP,AND,COMPOSITE_TEST,<Unused>,TEST_CLAUSE,"TEST PLACENAME ATTRIBUTE_IS_MISSING """"
      TEST ADMIN ATTRIBUTE_IS_MISSING """"",Both Missing
    DEFAULT_VALUE = <UNFILTERED>
    ADMIN AND PLACENAME ATTRIBUTE_HAS_VALUE -> TestFilter_2
    PLACENAME ONLY ATTRIBUTE_HAS_VALUE -> AttributeCreator_4
    ADMIN ONLY ATTRIBUTE_HAS_VALUE -> AttributeCreator_6
    Both Missing -> TestFilter_5_Both_Missing
    <UNFILTERED> -> dropped (writer CSV2_2)
TestFilter_2
    TEST_LIST = BOOL_OP,OR,COMPOSITE_TEST,<Unused>,TEST_CLAUSE,"TEST @Value(ADMIN) = @Value(PLACENAME)",@Value(ADMIN) = @Value(PLACENAME)
    DEFAULT_VALUE = <UNFILTERED>
    @Value(ADMIN) = @Value(PLACENAME) -> AttributeCreator_2
    <UNFILTERED> -> AttributeCreator_7
AttributeCreator_2
    ATTR_TABLE = SET_TO STREET_LOOKUP = @Value(NAME), @Value(PLACENAME)
    -> Reprojector_8
AttributeCreator_7
    ATTR_TABLE = SET_TO STREET_LOOKUP = @Value(NAME), @Value(PLACENAME), @Value(ADMIN)
    -> Reprojector_8
AttributeCreator_4
    ATTR_TABLE = SET_TO STREET_LOOKUP = @Value(NAME), @Value(PLACENAME)
    -> Reprojector_8
AttributeCreator_6
    ATTR_TABLE = SET_TO STREET_LOOKUP = @Value(NAME), @Value(ADMIN)
    -> Reprojector_8
Reprojector_8
    SOURCE = Read from feature
    RASTER_CELL_SIZE = Preserve Cells
    DEST = BritishNatGrid
    INTERPOLATION_TYPE_NAME = Nearest Neighbor
    REPROJECTED -> VertexCreator_4
VertexCreator_4
    MODE_NAME = Replace with Point
    YVAL = @Value(End_y)
    XVAL = @Value(End_x)
    -> AttributeCreator_5
AttributeCreator_5
    ATTR_TABLE:
      SET_TO X_CENTRE = @Evaluate((@Value(End_x._max)+@Value(End_x._min))/2)
      SET_TO Y_CENTRE = @Evaluate((@Value(End_y._max)+@Value(End_y._min))/2)
    -> Reprojector_9
Reprojector_9
    SOURCE = Read from feature
    RASTER_CELL_SIZE = Preserve Cells
    DEST = BritishNatGrid
    INTERPOLATION_TYPE_NAME = Nearest Neighbor
    REPROJECTED -> VertexCreator_5
    REPROJECTED -> DuplicateFilter
VertexCreator_5
    MODE_NAME = Replace with Point
    YVAL = @Value(End_y)
    XVAL = @Value(End_x)
    -> NeighborFinder_2 [CANDIDATE]
DuplicateFilter
    KEYATTR = STREET_LOOKUP
    INPUT_ORDERED_CHOICE = No
    UNIQUE -> AttributeKeeper_4
AttributeKeeper_4
    KEEP_ATTRS = Y_CENTRE,X_CENTRE,STREET_LOOKUP
    -> VertexCreator_6
VertexCreator_6
    MODE_NAME = Replace with Point
    YVAL = @Value(Y_CENTRE)
    XVAL = @Value(X_CENTRE)
    -> NeighborFinder_2 [BASE]
NeighborFinder_2
    MEASURE_TYPE = Continuous
    MODE = Bases and Candidates
    INSERT_VERTEX = No
    ATTR_CONFLICT_RES = Use Base
    GROUP_BY = STREET_LOOKUP
    K = 1
    ATTR_ACCUM_MODE = Merge Candidate
    CANDIDATES_FIRST = No
    MEASURES_FROM_CANDIDATE = Yes
    TREAT_POLYGON_AS = Lines
    MATCHED -> VertexCreator_7
VertexCreator_7
    MODE_NAME = Replace with Point
    YVAL = @Value(End_y)
    XVAL = @Value(End_x)
    -> AttributeRenamer
AttributeRenamer
    ATTR_TABLE:
      RENAME_SET_DEFAULT End_y > Y_COORD
      RENAME_SET_DEFAULT End_x > X_COORD
    -> Step2_out_v7 (writer CSV2_2)
Step2_out_v7 (writer CSV2_2)
    attributes: NAME string, ID string, PLACENAME string, ADMIN string, STREET_LOOKUP string, X_COORD string, Y_COORD string, SHIELDNUM string
TestFilter_5_Both_Missing: Inspector
dropped (writer CSV2_2)
    attributes: NAME string, ID string, PLACENAME string, ADMIN string, STREET_LOOKUP string, X_COORD string, Y_COORD string

FME custom transformer LoopFilter_2
Tests whether a line is a loop, i.e. whether its end matches the beginning.
The transformers outputs loops through PASSED port, and non-loops through FAILED port.
An isLoop attribute is added to each feature. 1 means the feature is loop, and zero means it is not.

LINE (input)
    -> LineFilter
Note: LoopFilter / Dmitri Bagh / July 11, 2005
LineFilter: GeometryFilter
    POINT -> NON-LINEAR (output)
    LINE -> LoopTester
    ARC -> NON-LINEAR (output)
    AREA -> NON-LINEAR (output)
    ELLIPSE -> NON-LINEAR (output)
    TEXT -> NON-LINEAR (output)
    NULL -> NON-LINEAR (output)
Note: LoopTester [ExpressionEvaluator:1] / _isLoop = (@Coordinate(x,0)-@Coordinate(x,-1))||(@Coordinate(y,0)-@Coordinate(y,-1)) / Version: 1
Note: Evaluates to 0 if feature is loop, and 1, if it is not.
LoopTester: ExpressionEvaluator
    VAL_ATTR = _isLoop
    EXPRESSION = (@Coordinate(x,0)-@Coordinate(x,-1))||(@Coordinate(y,0)-@Coordinate(y,-1))
    -> TESTER
Note: TESTER [Tester:1] / Test Description: <not set> / TEST &_isLoop = 0 / Condition: OR / Composite Test Expression: <not set> / Version: 1
TESTER: Tester
    TEST_CLAUSE = TEST &_isLoop = 0
    TEST_LIST = &_isLoop,=,0
    BOOL_OP = OR
    TEST_MODE = Automatic
    PASSED -> PASSED (output)
    FAILED -> FAILED (output)
PASSED (output)
FAILED (output)
NON-LINEAR (output)
