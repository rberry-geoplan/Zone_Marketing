FME workspace StreetLookup_step1.fmw

Parameters:
- DestDataset_CSV2 = $(FME_MF_DIR)R65   # Destination CSV (Comma Separated Value) Folder
- SourceDataset_ESRISHAPE_9 = ""$(FME_MF_DIR)TOMTOM\Built Up Areas\gbrg21___________bu.shp" "$(FME_MF_DIR)TOMTOM\Built Up Areas\gbrg23___________bu.shp" "$(FME_MF_DIR)TOMTOM\Built Up Areas\gbrg24___________bu.shp" "$(FME_MF_DIR)TOMTOM\Built Up Areas\gbrg26___________bu.shp" "$(FME_MF_DIR)TOMTOM\Built Up Areas\gbrg27___________bu.shp" "$(FME_MF_DIR)TOMTOM\Built Up Areas\gbrg28___________bu.shp" "$(FME_MF_DIR)TOMTOM\Built Up Areas\gbrg29___________bu.shp" "$(FME_MF_DIR)TOMTOM\Built Up Areas\gbrg30___________bu.shp""   # Source Esri Shapefile(s)
- FEATURE_TYPES_2 =
- SourceDataset_ESRISHAPE_6 = ""$(FME_MF_DIR)TOMTOM\Admin\gbrg21___________a8.shp" "$(FME_MF_DIR)TOMTOM\Admin\gbrg23___________a8.shp" "$(FME_MF_DIR)TOMTOM\Admin\gbrg24___________a8.shp" "$(FME_MF_DIR)TOMTOM\Admin\gbrg26___________a8.shp" "$(FME_MF_DIR)TOMTOM\Admin\gbrg27___________a8.shp" "$(FME_MF_DIR)TOMTOM\Admin\gbrg28___________a8.shp" "$(FME_MF_DIR)TOMTOM\Admin\gbrg29___________a8.shp" "$(FME_MF_DIR)TOMTOM\Admin\gbrg30___________a8.shp""   # Source Esri Shapefile(s)
- FEATURE_TYPES_3 =
- DestDataset_MAPINFO = $(FME_MF_DIR)StreetLookup   # Destination MapInfo Folder
- SourceDataset_ESRISHAPE_8 = ""$(FME_MF_DIR)TOMTOM\Road Network Files\gbrg21___________nw.shp" "$(FME_MF_DIR)TOMTOM\Road Network Files\gbrg23___________nw.shp" "$(FME_MF_DIR)TOMTOM\Road Network Files\gbrg24___________nw.shp" "$(FME_MF_DIR)TOMTOM\Road Network Files\gbrg26___________nw.shp" "$(FME_MF_DIR)TOMTOM\Road Network Files\gbrg27___________nw.shp" "$(FME_MF_DIR)TOMTOM\Road Network Files\gbrg28___________nw.shp" "$(FME_MF_DIR)TOMTOM\Road Network Files\gbrg29___________nw.shp" "$(FME_MF_DIR)TOMTOM\Road Network Files\gbrg30___________nw.shp""   # Source Esri Shapefile(s)
- FEATURE_TYPES_5 =

Readers:
- ESRISHAPE_1: ESRISHAPE from $(SourceDataset_ESRISHAPE_9)
- ESRISHAPE_2: ESRISHAPE from $(SourceDataset_ESRISHAPE_6)
- ESRISHAPE_3: ESRISHAPE from $(SourceDataset_ESRISHAPE_8) in LL-WGS84

Writers:
- CSV2_1: CSV2 to $(DestDataset_CSV2)
- MAPINFO_2: MAPINFO to $(DestDataset_MAPINFO) in BritishNatGrid

gbrg21___________nw (reader ESRISHAPE_3)
    attributes: ID number(15,0), FEATTYP short, FT short, F_JNCTID number(15,0), F_JNCTTYP short, T_JNCTID number(15,0), T_JNCTTYP short, PJ short, METERS double, FRC short, NETCLASS short, NETBCLASS short, NET2CLASS short, NAME char(100), NAMELC char(3), SOL short, NAMETYP short, CHARGE char(2), SHIELDNUM char(50), RTETYP short, RTEDIR char(2), RTEDIRVD char(2), PROCSTAT short, FOW short, SLIPRD short, FREEWAY short, BACKRD short, TOLLRD short, RDCOND short, STUBBLE short,
      PRIVATERD short, CONSTATUS char(2), ONEWAY char(2), F_BP short, T_BP short, F_ELEV short, T_ELEV short, KPH short, MINUTES float, POSACCUR short, CARRIAGE char(1), LANES short, RAMP short, ADA short, TRANS short, DYNSPEED short, SPEEDCAT short, NTHRUTRAF short, ROUGHRD short, PARTSTRUC short
    -> TestFilter_7
TestFilter_7
    TEST_LIST = BOOL_OP,OR,COMPOSITE_TEST,<Unused>,TEST_CLAUSE,"TEST @Value(FEATTYP) = 4110",4110
    DEFAULT_VALUE = <UNFILTERED>
    4110 -> TestFilter_8
TestFilter_8
    TEST_LIST:
      BOOL_OP,OR,COMPOSITE_TEST,<Unused>,TEST_CLAUSE,"TEST @Value(FRC) = 1
      TEST @Value(FRC) = 2
      TEST @Value(FRC) = 3
      TEST @Value(FRC) = 4
      TEST @Value(FRC) = 5
      TEST @Value(FRC) = 6
      TEST @Value(FRC) = 7
      TEST @Value(FRC) = 8
      TEST @Value(FRC) = 0",VALID FRC
    DEFAULT_VALUE = <UNFILTERED>
    VALID FRC -> AttributeKeeper_3
AttributeKeeper_3
    KEEP_ATTRS = NAME,SHIELDNUM,ID
    -> Reprojector_4
Reprojector_4
    INTERPOLATION_TYPE_NAME = Nearest Neighbor
    RASTER_CELL_SIZE = Preserve Cells
    DEST = BritishNatGrid
    SOURCE = Read from feature
    REPROJECTED -> TestFilter
TestFilter
    TEST_LIST:
      BOOL_OP,AND,COMPOSITE_TEST,<Unused>,TEST_CLAUSE,"TEST NAME ATTRIBUTE_IS_EMPTY """"
      TEST SHIELDNUM ATTRIBUTE_IS_EMPTY """"",NAME and Shield Blank,BOOL_OP,AND,COMPOSITE_TEST,<Unused>,TEST_CLAUSE,"TEST @Value(NAME) ATTRIBUTE_HAS_VALUE """"
      TEST @Value(SHIELDNUM) ATTRIBUTE_HAS_VALUE """"",NAME and Shield have a value,BOOL_OP,AND,COMPOSITE_TEST,<Unused>,TEST_CLAUSE,"TEST NAME ATTRIBUTE_IS_EMPTY """"
      TEST @Value(SHIELDNUM) ATTRIBUTE_HAS_VALUE """"",SHIELD ONLY,BOOL_OP,AND,COMPOSITE_TEST,<Unused>,TEST_CLAUSE,"TEST @Value(NAME) ATTRIBUTE_HAS_VALUE """"
      TEST SHIELDNUM ATTRIBUTE_IS_EMPTY """"",NAME ONLY
    DEFAULT_VALUE = <UNFILTERED>
    NAME and Shield have a value -> TestFilter_3
    SHIELD ONLY -> AttributeCreator_3
    NAME ONLY -> AttributeRemover
    <UNFILTERED> -> TestFilter__Unfiltered_
TestFilter_3
    TEST_LIST = BOOL_OP,OR,COMPOSITE_TEST,<Unused>,TEST_CLAUSE,"TEST @Value(NAME) = @Value(SHIELDNUM)",@Value(NAME) = @Value(SHIELDNUM)
    DEFAULT_VALUE = <UNFILTERED>
    @Value(NAME) = @Value(SHIELDNUM) -> AttributeRemover
    <UNFILTERED> -> AttributeCreator_2
AttributeCreator_2
    ATTR_TABLE = SET_TO NAME = @Value(NAME), @Value(SHIELDNUM)
    -> AttributeRemover
AttributeCreator_3
    ATTR_TABLE = SET_TO NAME = @Value(SHIELDNUM)
    -> AttributeRemover
AttributeRemover
    -> SpatialRelator [Requestor]
TestFilter__Unfiltered_: Inspector
gbrg21___________bu (reader ESRISHAPE_1)
    attributes: ID number(15,0), FEATTYP short, FEATAREA number(15,0), FEATPERIM number(15,0), NAME char(100), NAMELC char(3), BUACODE char(15)
    -> Reprojector_2
Reprojector_2
    INTERPOLATION_TYPE_NAME = Nearest Neighbor
    RASTER_CELL_SIZE = Preserve Cells
    DEST = BritishNatGrid
    SOURCE = Read from feature
    REPROJECTED -> AttributeKeeper
AttributeKeeper
    KEEP_ATTRS = NAME
    -> AttributeRenamer
AttributeRenamer
    ATTR_TABLE = RENAME_SET_DEFAULT NAME > PLACENAME
    -> SpatialRelator [Supplier]
    -> SpatialRelator_3 [Supplier]
SpatialRelator
    SUCCESS_ATTR = _related_candidates
    PREDICATES = WITHIN
    AGGREGATE_HANDLING = Yes
    ATTR_ACCUM_MODE = Merge Supplier
    ATTR_CONFLICT_RES = Use Requestor
    CALC_CARD = No
    CURVE_BOUNDARY_RULE_PARAM = Default Rule
    -> TestFilter_4
TestFilter_4
    TEST_LIST = BOOL_OP,OR,COMPOSITE_TEST,<Unused>,TEST_CLAUSE,"TEST @Value(_related_candidates) = 0",_related_candidates ATTRIBUTE_IS_EMPTY
    DEFAULT_VALUE = <UNFILTERED>
    _related_candidates ATTRIBUTE_IS_EMPTY -> SpatialRelator_3 [Requestor]
    <UNFILTERED> -> SpatialRelator_2 [Requestor]
SpatialRelator_3
    SUCCESS_ATTR = _related_candidates
    PREDICATES = TOUCHES
    AGGREGATE_HANDLING = Yes
    ATTR_ACCUM_MODE = Merge Supplier
    ATTR_CONFLICT_RES = Use Requestor
    CALC_CARD = No
    CURVE_BOUNDARY_RULE_PARAM = Default Rule
    -> SpatialRelator_2 [Requestor]
gbrg21___________a8 (reader ESRISHAPE_2)
    attributes: ID number(15,0), FEATTYP short, ORDER00 char(3), ORDER01 char(11), ORDER02 char(11), ORDER03 char(11), ORDER04 char(11), ORDER05 char(11), ORDER06 char(11), ORDER07 char(11), ORDER08 char(11), FEATAREA number(15,0), FEATPERIM number(15,0), NAME char(100), NAMELC char(3), POPCLASS short, POP long, CITYCENTER number(15,0)
    -> Reprojector_3
Reprojector_3
    INTERPOLATION_TYPE_NAME = Nearest Neighbor
    RASTER_CELL_SIZE = Preserve Cells
    DEST = BritishNatGrid
    SOURCE = Read from feature
    REPROJECTED -> AttributeKeeper_2
AttributeKeeper_2
    KEEP_ATTRS = NAME
    -> AttributeRenamer_2
AttributeRenamer_2
    ATTR_TABLE = RENAME_SET_DEFAULT NAME > ADMIN
    -> SpatialRelator_2 [Supplier]
    -> SpatialRelator_4 [Supplier]
SpatialRelator_2
    SUCCESS_ATTR = _related_candidates
    PREDICATES = WITHIN
    AGGREGATE_HANDLING = Yes
    ATTR_ACCUM_MODE = Merge Supplier
    ATTR_CONFLICT_RES = Use Requestor
    CALC_CARD = No
    CURVE_BOUNDARY_RULE_PARAM = Default Rule
    -> TestFilter_6
TestFilter_6
    TEST_LIST = BOOL_OP,OR,COMPOSITE_TEST,<Unused>,TEST_CLAUSE,"TEST @Value(_related_candidates) = 0",_related_candidates ATTRIBUTE_IS_EMPTY
    DEFAULT_VALUE = <UNFILTERED>
    _related_candidates ATTRIBUTE_IS_EMPTY -> SpatialRelator_4 [Requestor]
    <UNFILTERED> -> Snipper_2
SpatialRelator_4
    SUCCESS_ATTR = _related_candidates
    PREDICATES = TOUCHES
    AGGREGATE_HANDLING = Yes
    ATTR_ACCUM_MODE = Merge Supplier
    ATTR_CONFLICT_RES = Use Requestor
    CALC_CARD = No
    CURVE_BOUNDARY_RULE_PARAM = Default Rule
    -> Snipper_2
Snipper_2
    DEAGGREGATE_INPUT = YES
    STARTLOCATIONATTR = 0
    MEASUREMENTTYPE = 2D
    SNIPMODE = Distance (Percentage)
    ENDLOCATIONATTR = 50
    -> CoordinateExtractor_2
CoordinateExtractor_2
    Y_ATTR = Start_y
    IND = 0
    MODE = Specify Coordinate
    X_ATTR = Start_x
    -> CoordinateExtractor_3
CoordinateExtractor_3
    Y_ATTR = End_y
    IND = -1
    MODE = Specify Coordinate
    X_ATTR = End_x
    -> Table1 (writer MAPINFO_2)
Table1 (writer MAPINFO_2)
    attributes: NAME char(100), ID decimal(15,0), PLACENAME char(99), ADMIN char(99), _related_candidates char(99), Start_x char(99), Start_y char(99), End_x char(99), End_y char(99), SHIELDNUM char(7)

FME custom transformer LoopFilter_2
Tests whether a line is a loop, i.e. whether its end matches the beginning.
The transformers outputs loops through PASSED port, and non-loops through FAILED port.
An isLoop attribute is added to each feature. 1 means the feature is loop, and zero means it is not.

LINE (input)
    -> LineFilter
Note: LoopFilter / Dmitri Bagh / July 11, 2005
LineFilter: GeometryFilter
    POINT -> NON-LINEAR (output)
    LINE -> LoopTester
    ARC -> NON-LINEAR (output)
    AREA -> NON-LINEAR (output)
    ELLIPSE -> NON-LINEAR (output)
    TEXT -> NON-LINEAR (output)
    NULL -> NON-LINEAR (output)
Note: LoopTester [ExpressionEvaluator:1] / _isLoop = (@Coordinate(x,0)-@Coordinate(x,-1))||(@Coordinate(y,0)-@Coordinate(y,-1)) / Version: 1
Note: Evaluates to 0 if feature is loop, and 1, if it is not.
LoopTester: ExpressionEvaluator
    VAL_ATTR = _isLoop
    EXPRESSION = (@Coordinate(x,0)-@Coordinate(x,-1))||(@Coordinate(y,0)-@Coordinate(y,-1))
    -> TESTER
Note: TESTER [Tester:1] / Test Description: <not set> / TEST &_isLoop = 0 / Condition: OR / Composite Test Expression: <not set> / Version: 1
TESTER: Tester
    TEST_LIST = &_isLoop,=,0
    TEST_MODE = Automatic
    BOOL_OP = OR
    TEST_CLAUSE = TEST &_isLoop = 0
    PASSED -> PASSED (output)
    FAILED -> FAILED (output)
PASSED (output)
FAILED (output)
NON-LINEAR (output)
